FME workspace none2none.fmw

Parameters:
- TARGET_URL = https://karttjanster.sveaskog.se/agspublic/rest/services   # Request URL

Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = text_line_data
    TARGET_ATTR_ENCODING = auto-detect
    TARGET_URL = $(TARGET_URL)?f=pjson
    TRANSFER_TIMEOUT_LENGTH = 90
    USE_COOKIES = No
    VERIFY_SSL_CERTIFICATES = Yes
    -> JSONExtractor
    -> FeatureWriter [text_line]
JSONExtractor
    EXTRACT_QUERY_TABLE = folders json["folders"]
    JSON_DOCUMENT = @Value(text_line_data)
    READ_FROM_FILE = NO
    EVALUATED -> JSONFragmenter
JSONFragmenter
    EXPLODE_FORMAT = JSON
    EXTRACT_ATTR = No
    JSON_ATTR = folders
    JSON_QUERY = json[*]
    READ_FROM_FILE = NO
    REJECT_EMPTY_LISTS = YES
    FRAGMENTS -> HTTPCaller_2
HTTPCaller_2
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = text_line_data
    TARGET_ATTR_ENCODING = auto-detect
    TARGET_URL = $(TARGET_URL)/@Value(folders)?f=pjson
    TRANSFER_TIMEOUT_LENGTH = 90
    USE_COOKIES = No
    VERIFY_SSL_CERTIFICATES = Yes
    -> AttributeCreator
    -> FeatureWriter_2 [text_line]
    -> JSONExtractor_2
JSONExtractor_2
    EXTRACT_QUERY_TABLE = services json["services"]
    JSON_DOCUMENT = @Value(text_line_data)
    READ_FROM_FILE = NO
    EVALUATED -> JSONFragmenter_2
JSONFragmenter_2
    EXPLODE_FORMAT = JSON
    EXTRACT_ATTR = No
    JSON_ATTR = services
    JSON_QUERY = json[*]
    READ_FROM_FILE = NO
    REJECT_EMPTY_LISTS = YES
    FRAGMENTS -> JSONExtractor_3
JSONExtractor_3
    EXTRACT_QUERY_TABLE = name json["name"] type json["type"]
    JSON_DOCUMENT = @Value(services)
    READ_FROM_FILE = NO
    EVALUATED -> AttributeCreator_2
    EVALUATED -> HTTPCaller_3
HTTPCaller_3
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = text_line_data
    TARGET_ATTR_ENCODING = auto-detect
    TARGET_URL = $(TARGET_URL)/@Value(name)/@Value(type)?f=pjson
    TRANSFER_TIMEOUT_LENGTH = 90
    USE_COOKIES = No
    VERIFY_SSL_CERTIFICATES = Yes
    -> FeatureWriter_5 [text_line]

Bookmark: fixture
FeatureWriter_5
    DATASET = $(FME_MF_DIR_ENCODED)fixtures\karttjanster\@Value(name)\@Value(type).json
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = Unix
    TEXTLINE_MIME_TYPE = text/plain
    TEXTLINE_OVERWRITE_FILE = YES
    TEXTLINE_WRITE_LAST_EOL = NO
    TEXTLINE_WRITE_UTF8_BOM = NO
    TOTAL_FEATURES_WRITTEN_ATTR = _total_features_written
FeatureWriter_2
    DATASET = $(FME_MF_DIR_ENCODED)fixtures\karttjanster\@Value(folders)\@Value(folders).json
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = Unix
    TEXTLINE_MIME_TYPE = text/plain
    TEXTLINE_OVERWRITE_FILE = YES
    TEXTLINE_WRITE_LAST_EOL = NO
    TEXTLINE_WRITE_UTF8_BOM = NO
    TOTAL_FEATURES_WRITTEN_ATTR = _total_features_written
FeatureWriter
    DATASET = $(FME_MF_DIR_ENCODED)fixtures\karttjanster\services.json
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = Unix
    TEXTLINE_MIME_TYPE = text/plain
    TEXTLINE_OVERWRITE_FILE = YES
    TEXTLINE_WRITE_LAST_EOL = NO
    TEXTLINE_WRITE_UTF8_BOM = NO
    TOTAL_FEATURES_WRITTEN_ATTR = _total_features_written

Bookmark: cy
AttributeCreator_2
    ATTR_TABLE:
      SET_TO text_line_data (buffer) = const RERUNS = 3;
        const URLSUFIX = Cypress.env('karttjansterSites');

        describe("@Value(name)", () => {
            URLSUFIX.forEach((urlsf) => {
                const KarttjansURL = `${Cypress.env('karttjansterBase')}${urlsf}.${Cypress.env('sveaDomain')}/${Cypress.env('karttjansterRest')}`;
                Cypress._.times(RERUNS, (index) => {
                    it(`@Value(type) - ${KarttjansURL}/services/@Value(name)/@Value(type)?f=pjson - Run ${index + 1}`, () => {
                        cy.fixture('karttjanster/@Value(name)/@Value(type)').then((fixture) => {
                            cy.log('Fixture data:', JSON.stringify(fixture));
                            cy.request({
                                method: 'GET',
                                url: `${KarttjansURL}/services/@Value(name)/@Value(type)?f=pjson`,
                                headers: {
                                    'Accept': 'application/json',
                                    'Content-Type': 'application/json'
                                }
                            })
                                .then((response) => {
                                    const parsedBody = JSON.parse(response.body);

                                    // Log specific parts
                                    cy.log('Response body:', parsedBody);

                                    // Assertions
                                    expect(response.status).to.eq(200);
                                    expect(parsedBody.currentVersion).to.eq(fixture.currentVersion);
                                    expect(parsedBody.layers).to.deep.equal(fixture.layers);
                                    expect(parsedBody.spatialReference).to.deep.equal(fixture.spatialReference);
                                    expect(parsedBody.tables).to.deep.equal(fixture.tables);
                                });
                        });
                    });
                });
            });
        });
    -> FeatureWriter_4 [text_line]
FeatureWriter_4
    DATASET = $(FME_MF_DIR_ENCODED)e2e\karttjanster\@Value(name)\@Value(type).cy.js
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = NO
    TOTAL_FEATURES_WRITTEN_ATTR = _total_features_written
AttributeCreator
    ATTR_TABLE:
      SET_TO text_line_data (buffer) = const RERUNS = 3;
        const URLSUFIX = Cypress.env('karttjansterSites');

        describe("Anmalan", () => {
            URLSUFIX.forEach((urlsf) => {
                const KarttjansURL = `${Cypress.env('karttjansterBase')}${urlsf}.${Cypress.env('sveaDomain')}/${Cypress.env('karttjansterRest')}`;
                Cypress._.times(RERUNS, (index) => {
                    it(`Services page - ${KarttjansURL}/services/@Value(folders)?f=pjson - Run ${index + 1}`, () => {
                        cy.fixture('karttjanster/@Value(folders)/@Value(folders)').then((fixture) => {
                            cy.log('Fixture data:', JSON.stringify(fixture));
                            cy.request({
                                method: 'GET',
                                url: `${KarttjansURL}/services/@Value(folders)?f=pjson`,
                                headers: {
                                    'Accept': 'application/json',
                                    'Content-Type': 'application/json'
                                }
                            })
                                .then((response) => {
                                    const parsedBody = JSON.parse(response.body);


                                    // Log the entire response
                                    cy.log('Response body:', parsedBody);

                                    // Assertions
                                    expect(response.status).to.eq(200);
                                    expect(parsedBody.currentVersion).to.eq(fixture.currentVersion);
                                    expect(parsedBody.services).to.deep.equal(fixture.services);

                                    // Additional checks
                                    expect(parsedBody).to.have.property('services').that.is.an('array');
                                });
                        });
                    });
                });
            });
        });
    -> FeatureWriter_3 [text_line]
FeatureWriter_3
    DATASET = $(FME_MF_DIR_ENCODED)e2e\karttjanster\@Value(folders)\@Value(folders).cy.js
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = NO
    TOTAL_FEATURES_WRITTEN_ATTR = _total_features_written
